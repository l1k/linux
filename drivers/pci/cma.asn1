-- SPDX-License-Identifier: BSD-3-Clause
--
-- Component Measurement and Authentication (CMA-SPDM, PCIe r6.1 sec 6.31.3)
-- X.509 Subject Alternative Name (RFC 5280 sec 4.2.1.6)
--
-- Copyright (C) 2008 IETF Trust and the persons identified as authors
-- of the code
--
-- https://www.rfc-editor.org/rfc/rfc5280#section-4.2.1.6
--
-- The ASN.1 module in RFC 5280 appendix A.1 uses EXPLICIT TAGS whereas the one
-- in appendix A.2 uses IMPLICIT TAGS.  The kernel's simplified asn1_compiler.c
-- always uses EXPLICIT TAGS, hence this ASN.1 module differs from RFC 5280 in
-- that it adds IMPLICIT to definitions from appendix A.2 (such as GeneralName)
-- and omits EXPLICIT in those definitions.

SubjectAltName ::= GeneralNames

GeneralNames ::= SEQUENCE OF GeneralName

GeneralName ::= CHOICE {
	otherName			[0] IMPLICIT OtherName,
	rfc822Name			[1] IMPLICIT IA5String,
	dNSName				[2] IMPLICIT IA5String,
	x400Address			[3] ANY,
	directoryName			[4] ANY,
	ediPartyName			[5] IMPLICIT EDIPartyName,
	uniformResourceIdentifier	[6] IMPLICIT IA5String,
	iPAddress			[7] IMPLICIT OCTET STRING,
	registeredID			[8] IMPLICIT OBJECT IDENTIFIER
	}

OtherName ::= SEQUENCE {
	type-id			OBJECT IDENTIFIER ({ pci_cma_note_oid }),
	value			[0] ANY ({ pci_cma_note_san })
	}

EDIPartyName ::= SEQUENCE {
	nameAssigner		[0] ANY OPTIONAL,
	partyName		[1] ANY
	}
